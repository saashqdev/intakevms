DELL-CPU DEFINITIONS ::= BEGIN

DELL OBJECT IDENTIFIER ::= { iso(1) org(3) dod(6) internet(1) private(4) enterprises(1) 674 }

cpu   OBJECT IDENTIFIER ::= {DELL 50}

-- CPU
CoresCount OBJECT-TYPE
        SYNTAX INTEGER
        ACCESS read-only
        STATUS mandatory
        DESCRIPTION
                 "CPU cores count"
        ::= {cpu 0}

CpuUsagePercent OBJECT-TYPE
        SYNTAX DisplayString
        ACCESS read-only
        STATUS mandatory
        DESCRIPTION
                 "CPU usage in percent"
        ::= {cpu 1}

END
